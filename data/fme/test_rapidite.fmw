FME workspace test_rapidite.fmw

Parameters:
- SourceDataset_GEOJSON =

Readers:
- GEOJSON_1: GEOJSON from $(SourceDataset_GEOJSON)

cadastre-17-parcelles (reader GEOJSON_1)
    attributes: id string, commune string, prefixe string, section string, numero string, contenance int, arpente boolean, created string, updated string
    -> Junction_2
    -> Junction_5
    -> Junction
    -> Junction_4
    -> Junction_6
Junction
    -> AttributeRenamer_3
    -> AttributeManager_5
    -> AttributeKeeper_4
    -> AttributeManager_7
    -> AttributeCreator_6
    -> AttributeManager_8
Junction_2
    -> AttributeManager_2
    -> AttributeCreator
    -> AttributeManager
    -> AttributeRenamer
    -> Junction_3
Junction_4
    -> AttributeRenamer_4
    -> AttributeCreator_8
    -> AttributeManager_10
    -> AttributeManager_11
Junction_5
    -> AttributeRenamer_2
    -> AttributeManager_9
Junction_6
    -> AttributeCreator_3
    -> AttributeManager_6

Bookmark: Test 2.1
AttributeRenamer_3
    ATTR_TABLE:
      RENAME_SET_DEFAULT commune > ccocom
      RENAME_SET_DEFAULT created > date_creation
      RENAME_SET_DEFAULT id > identifiant_unique
      RENAME_SET_DEFAULT updated > mise_a_jour
    MISSING_INPUT_ATTRS = REMOVE
    -> AttributeCreator_5
AttributeCreator_5
    ATTR_TABLE:
      SET_TO Attribut 1 = Test
      SET_TO Attribut 2 = @Value(arpente)
      SET_TO Attribut 3 = @Value(Attribut 1) + @Value(Attribut 2)
      SET_TO Attribut 4 = @Evaluate(@Value(mise_a_jour)-@Value(date_creation))
AttributeManager_5
    ATTR_TABLE:
      SET_TO id = identifiant_unique
      SET_TO commune = ccocom
      SET_TO created = date_creation
      SET_TO updated = mise_a_jour
      SET_TO Attribute 1 = Test
      SET_TO Attribute 2 = @Value(arpente)
      SET_TO Attribute 3 = @Value(Attribute 1)+@Value(Attribute 2)
      SET_TO Attribute 4 = @Evaluate(@Value(contenance)*@Value(numero))

Bookmark: Test 2.2
AttributeKeeper_4
    CREATE_BULK_MODE_FEATURES = NO
    KEEP_ATTRS = arpente,created,id,updated
    -> AreaCalculator_3
AreaCalculator_3
    AREA_ATTR = _area
    AREA_TYPE = Plane Area
    MULT = 1
AttributeManager_7
    ATTR_TABLE:
      REMOVE commune
      REMOVE prefixe
      REMOVE section
      REMOVE numero
      REMOVE contenance

Bookmark: Test 2.3
AttributeCreator_6
    ATTR_TABLE:
      SET_TO Attribut 1 = Test
      SET_TO Attribut 2 = @Value(arpente)
      SET_TO Attribut 3 = @Value(Attribut 1) + @Value(Attribut 2)
      SET_TO Attribut 4 = @Evaluate(@Value(updated)-@Value(created))
    -> AttributeKeeper_5
AttributeKeeper_5
    CREATE_BULK_MODE_FEATURES = NO
    KEEP_ATTRS = arpente,Attribut 1,Attribut 2,Attribut 3,Attribut 4,commune,created,id,updated,contenance,numero
AttributeManager_8
    ATTR_TABLE:
      SET_TO id
      SET_TO commune
      REMOVE prefixe
      REMOVE section
      SET_TO created
      SET_TO updated
      SET_TO Attribute 1 = Test
      SET_TO Attribute 2 = @Value(arpente)
      SET_TO Attribute 3 = @Value(Attribute 1)+@Value(Attribute 2)
      SET_TO Attribute 4 = @Evaluate(@Value(contenance)*@Value(numero))

Bookmark: Test 1.1
AttributeRenamer
    ATTR_TABLE:
      RENAME_SET_DEFAULT commune > ccocom
      RENAME_SET_DEFAULT created > date_creation
      RENAME_SET_DEFAULT id > identifiant_unique
      RENAME_SET_DEFAULT updated > mise_a_jour
    MISSING_INPUT_ATTRS = REMOVE
AttributeManager
    ATTR_TABLE:
      RENAME_SET_VALUE id > identifiant_unique
      RENAME_SET_VALUE commune > ccocom
      RENAME_SET_VALUE created > date_creation
      RENAME_SET_VALUE updated > mise_a_jour

Bookmark: Test mono Transformer
Junction_3
    -> AreaCalculator
    -> AttributeKeeper
    -> AttributeManager_3
    -> AttributeManager_4

Bookmark: Test 1.3
AttributeKeeper
    CREATE_BULK_MODE_FEATURES = NO
    KEEP_ATTRS = commune,section
AttributeManager_3
    ATTR_TABLE:
      REMOVE id
      REMOVE prefixe
      REMOVE numero
      REMOVE contenance
      REMOVE arpente
      REMOVE created
      REMOVE updated

Bookmark: Test 1.4
AreaCalculator
    AREA_ATTR = _area
    AREA_TYPE = Plane Area
    MULT = 1
AttributeManager_4
    ATTR_TABLE = SET_TO _area = @Evaluate(@Area())

Bookmark: Test 1.2
AttributeCreator
    ATTR_TABLE:
      SET_TO Attribut 1 = Test
      SET_TO Attribut 2 = @Value(arpente)
      SET_TO Attribut 3 = @Value(Attribut 1) + @Value(Attribut 2)
      SET_TO Attribut 4 = @Evaluate(@Value(updated)-@Value(created))
AttributeManager_2
    ATTR_TABLE:
      SET_TO Attribut 1 = Test
      SET_TO Attribut 2 = @Value(arpente)
      SET_TO Attribut 3 = @Value(Attribut 1)+@Value(Attribut 2)
      SET_TO Attribut 4 = @Evaluate(@Value(updated)-@Value(created))

Bookmark: Test 3.1
AttributeRenamer_4
    ATTR_TABLE:
      RENAME_SET_DEFAULT commune > ccocom
      RENAME_SET_DEFAULT created > date_creation
      RENAME_SET_DEFAULT id > identifiant_unique
      RENAME_SET_DEFAULT updated > mise_a_jour
    MISSING_INPUT_ATTRS = REMOVE
    -> AttributeCreator_7
AttributeCreator_7
    ATTR_TABLE:
      SET_TO Attribut 1 = Test
      SET_TO Attribut 2 = @Value(arpente)
      SET_TO Attribut 3 = @Value(Attribut 1) + @Value(Attribut 2)
      SET_TO Attribut 4 = @Evaluate(@Value(mise_a_jour)-@Value(date_creation))
    -> AttributeKeeper_6
AttributeKeeper_6
    CREATE_BULK_MODE_FEATURES = NO
    KEEP_ATTRS = ccocom,arpente,Attribut 1,Attribut 2,Attribut 3,Attribut 4,date_creation,identifiant_unique,mise_a_jour
AttributeManager_11
    ATTR_TABLE:
      RENAME_SET_VALUE id > identifiant_unique
      RENAME_SET_VALUE commune > ccocom
      REMOVE prefixe
      REMOVE section
      REMOVE numero
      REMOVE contenance
      RENAME_SET_VALUE created > date_creation
      RENAME_SET_VALUE updated > mise_a_jour
      SET_TO Attribut 1 = Test
      SET_TO Attribut 2 = @Value(arpente)
      SET_TO Attribut 3 = @Value(Attribut 1)+@Value(Attribut 2)
      SET_TO Attribut 4 = @Evaluate(@Value(mise_a_jour)-@Value(date_creation))

Bookmark: Test 3.1
AttributeCreator_8
    ATTR_TABLE:
      SET_TO Attribut 1 = Test
      SET_TO Attribut 2 = @Value(arpente)
      SET_TO Attribut 3 = @Value(Attribut 1) + @Value(Attribut 2)
      SET_TO Attribut 4 = @Evaluate(@Value(updated)-@Value(created))
    -> AttributeKeeper_7
AttributeKeeper_7
    CREATE_BULK_MODE_FEATURES = NO
    KEEP_ATTRS = arpente,Attribut 1,Attribut 2,Attribut 3,Attribut 4,commune,created,id,updated
    -> AreaCalculator_4
AreaCalculator_4
    AREA_ATTR = _area
    AREA_TYPE = Plane Area
    MULT = 1
AttributeManager_10
    ATTR_TABLE:
      REMOVE prefixe
      REMOVE section
      REMOVE numero
      REMOVE contenance
      SET_TO Attribut 1 = Test
      SET_TO Attribut 2 = @Value(arpente)
      SET_TO Attribut 3 = @Value(Attribut 1)+@Value(Attribut 2)
      SET_TO Attribut 4 = @Evaluate(@Value(updated)-@Value(created))
      SET_TO _area = @Evaluate(@Area())

Bookmark: Test 4
AttributeRenamer_2
    ATTR_TABLE:
      RENAME_SET_DEFAULT commune > ccocom
      RENAME_SET_DEFAULT created > date_creation
      RENAME_SET_DEFAULT id > identifiant_unique
      RENAME_SET_DEFAULT updated > mise_a_jour
    MISSING_INPUT_ATTRS = REMOVE
    -> AttributeCreator_2
AttributeCreator_2
    ATTR_TABLE:
      SET_TO Attribut 1 = Test
      SET_TO Attribut 2 = @Value(arpente)
      SET_TO Attribut 3 = @Value(Attribut 1) + @Value(Attribut 2)
      SET_TO Attribut 4 = @Evaluate(@Value(mise_a_jour)-@Value(date_creation))
    -> AttributeKeeper_2
AttributeKeeper_2
    CREATE_BULK_MODE_FEATURES = NO
    KEEP_ATTRS = ccocom,arpente,Attribut 1,Attribut 2,Attribut 3,Attribut 4,date_creation,identifiant_unique,mise_a_jour
    -> AreaCalculator_2
AreaCalculator_2
    AREA_ATTR = _area
    AREA_TYPE = Plane Area
    MULT = 1
AttributeManager_9
    ATTR_TABLE:
      RENAME_SET_VALUE id > identifiant_unique
      RENAME_SET_VALUE commune > ccocom
      REMOVE prefixe
      REMOVE section
      REMOVE numero
      REMOVE contenance
      RENAME_SET_VALUE created > date_creation
      RENAME_SET_VALUE updated > mise_a_jour
      SET_TO Attribut 1 = Test
      SET_TO Attribut 2 = @Value(arpente)
      SET_TO Attribut 3 = @Value(Attribut 1)+@Value(Attribut 2)
      SET_TO Attribut 4 = @Evaluate(@Value(mise_a_jour)-@Value(date_creation))
      SET_TO _area = @Evaluate(@Area())

Bookmark: Test 2 AM
AttributeCreator_3
    ATTR_TABLE:
      SET_TO Attribut 1 = Test
      SET_TO Attribut 2 = @Value(arpente)
      SET_TO Attribut 3 = @Value(Attribut 1) + @Value(Attribut 2)
    -> AttributeKeeper_3
AttributeKeeper_3
    CREATE_BULK_MODE_FEATURES = NO
    KEEP_ATTRS = Attribut 3
AttributeManager_6
    ATTR_TABLE:
      SET_TO Attribut 1 = Test
      SET_TO Attribut 2 = @Value(arpente)
      SET_TO Attribut 3 = @Value(Attribut 1)+@Value(Attribut 2)
    -> AttributeManager_12
AttributeManager_12
    ATTR_TABLE:
      REMOVE id
      REMOVE commune
      REMOVE prefixe
      REMOVE section
      REMOVE numero
      REMOVE contenance
      REMOVE arpente
      REMOVE created
      REMOVE updated
      REMOVE Attribut 1
      REMOVE Attribut 2
